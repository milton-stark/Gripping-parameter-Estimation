import FreeCAD as App
import FreeCADGui as Gui
import Part
import json
import os
from PySide import QtGui

# =========================
# CONFIGURATION
# =========================
DENSITY_KG_PER_M3 = 2700   # Aluminium
MU = 0.5
SAFETY = 2.0
G = 9.80665

PRE_GRIP_OFFSET_MM = 20.0   # 5mm above the top surface
POST_CLEARANCE_MM = 15.0
RELEASE_HEIGHT_MM = 25.0
SPHERE_RADIUS = 1.5
AXIS_LENGTH = 50.0 
ROUND = 6

VIS_PREFIX = "GRIP_VIZ_"

# =========================
# HELPERS
# =========================
def r(x): return round(x, ROUND)

def vec(v):
    return [r(v.x), r(v.y), r(v.z)]

def clear_visuals():
    doc = App.ActiveDocument
    for o in doc.Objects:
        if o.Name.startswith(VIS_PREFIX):
            doc.removeObject(o.Name)

def make_sphere(name, pos, color):
    doc = App.ActiveDocument
    s = doc.addObject("Part::Sphere", VIS_PREFIX + name)
    s.Radius = SPHERE_RADIUS
    s.Placement.Base = pos
    s.ViewObject.ShapeColor = color
    s.ViewObject.Transparency = 30
    return s

def make_axis_line(name, start, direction, color=(1.0, 1.0, 0.0)):
    doc = App.ActiveDocument
    end = start + direction.multiply(AXIS_LENGTH)
    line = Part.makeLine(start, end)
    obj = doc.addObject("Part::Feature", VIS_PREFIX + name)
    obj.Shape = line
    obj.ViewObject.LineColor = color
    obj.ViewObject.LineWidth = 2
    return obj

# =========================
# MAIN
# =========================
def main():
    doc = App.ActiveDocument
    if not doc:
        App.Console.PrintError("No active document.\n")
        return

    sel = Gui.Selection.getSelection()
    if not sel:
        App.Console.PrintError("Please select the Mesh or Object in the tree.\n")
        return

    obj = sel[0]
    
    # --- FILE DIALOG ---
    default_path = os.path.join(os.path.expanduser("~"), f"{obj.Label}_grip_data.json")
    file_path, _ = QtGui.QFileDialog.getSaveFileName(None, "Save JSON", default_path, "JSON (*.json)")
    if not file_path: return

    clear_visuals()

    # --- GEOMETRY DATA EXTRACTION ---
    if hasattr(obj, "Mesh"):
        mesh = obj.Mesh
        bb = mesh.BoundBox
        com = bb.Center
        volume_mm3 = mesh.Volume
    elif hasattr(obj, "Shape"):
        shape = obj.Shape
        bb = shape.BoundBox
        com = shape.CenterOfMass
        volume_mm3 = shape.Volume
    else:
        App.Console.PrintError("Object type not supported.\n")
        return

    # --- CALCULATION LOGIC ---
    # Top Surface Z coordinate
    z_max = bb.ZMax
    
    # Pre-Grip: 5mm above top surface
    pre_grip_world_z = z_max + PRE_GRIP_OFFSET_MM
    # Convert to relative (distance from COM to Pre-Grip)
    pre_z_relative = pre_grip_world_z - com.z
    
    # Post-Grip: (Using previous logic or specific offset)
    post_z_relative = (z_max - com.z) - 10.0
    
    # Mass & Force
    volume_m3 = abs(volume_mm3) * 1e-9
    mass = volume_m3 * DENSITY_KG_PER_M3
    f_per_jaw = (mass * G * SAFETY) / (2 * MU)

    # --- JSON DATA ---
    data = {
        "object_id": f"{obj.Label}_grip_COM",
        "relative_to_tcp": vec(com),
        "source": "freecad_grip_macro_COM_weighted",
        "units": "mm, N",
        "geometry": {
            "bounding_box_mm": [r(bb.XLength), r(bb.YLength), r(bb.ZLength)],
            "center_mm": [0.0, 0.0, 0.0],
            "principal_axis_world": {
                "axis_dir_unit": [0.0, 0.0, 1.0]
            }
        },
        "grasp_parameters": {
            "grip_point_mm": [0.0, 0.0, 0.0],
            "pre_grip_mm": [0.0, 0.0, r(pre_z_relative)],
            "post_grip_mm": [0.0, 0.0, r(post_z_relative)],
            "release_height_mm": RELEASE_HEIGHT_MM
        },
        "force_estimation": {
            "mass_kg": r(mass),
            "friction_coefficient": MU,
            "safety_factor": SAFETY,
            "normal_force_per_jaw_N": r(f_per_jaw),
            "total_normal_force_both_jaws_N": r(2 * f_per_jaw)
        },
        "post_grip_logic": {
            "zmax_of_object": r(z_max),
            "pre_grip_offset_mm": PRE_GRIP_OFFSET_MM,
            "post_clearance_mm": POST_CLEARANCE_MM,
            "final_post_z_mm": r(z_max + POST_CLEARANCE_MM)
        }
    }

    # --- SAVE ---
    with open(file_path, "w") as f:
        json.dump(data, f, indent=4)

    # --- VISUALIZATION ---
    make_sphere("GRIP_POINT", com, (1.0, 0.0, 0.0))    # Red
    make_sphere("PRE_GRIP", App.Vector(com.x, com.y, pre_grip_world_z), (0.2, 0.4, 1.0))  # Blue
    make_sphere("POST_GRIP", com + App.Vector(0, 0, post_z_relative), (0.2, 0.8, 0.2)) # Green
    make_axis_line("MOTION_AXIS_Z", com, App.Vector(0, 0, 1))

    doc.recompute()
    App.Console.PrintMessage(f"✅ Exported to: {file_path}\n")
    App.Console.PrintMessage(f"📍 Pre-Grip set to {PRE_GRIP_OFFSET_MM}mm above Z-Max ({r(z_max)})\n")

if __name__ == "__main__":
    main()
